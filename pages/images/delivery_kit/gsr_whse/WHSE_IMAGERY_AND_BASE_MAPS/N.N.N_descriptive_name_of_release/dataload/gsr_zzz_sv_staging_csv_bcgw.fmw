FME workspace gsr_zzz_sv_staging_csv_bcgw.fmw
Title: GSR_zzz_SVW_staging_csv_bcgw
Description: Use this as a starting point for loading records for the zzz GSR occupant type into the BCGW. 
Fill in 
BUSINESS_ID 
CUSTODIAN_ID
hasSourceDataID (= Y if the primary key id in the CSV is maintained on the operational side; N if it has to be generated as part of the load)
SRC_DATASET_CSV_1  (CSV file in the staging area)
DEST_FEATURE_1 (name of the spatail view)
DEST_FEATURE_2 (name of the internal non-core column view)
FAILURE_MESSAGE and/or FAILURE_EMAIL if the defaults aren't appropriate
Usage: Describe processing summary
History: June 26, 2013,G. Gale, DataBC,release 12.3 template for file sources,Sept 11, 2014,G. Gale, DataBC,release 13.1 template for file sources,,,developed script for
Startup Python:
      import fme
      import DataBCFMWTemplate
      start = DataBCFMWTemplate.Start(fme)
      start.startup()
Shutdown Python:
      import fme
      import DataBCFMWTemplate
      shutIt = DataBCFMWTemplate.Shutdown(fme)
      shutIt.shutdown()

Parameters:
- BUSINESS_ID = -1   # Business ID
- CUSTODIAN_ID = -1   # Custodian ID
- hasSourceDataID = fill in Y or N   # Has Source Data ID?
- SRC_DATASET_CSV_1 = \\data.bcgov\data_staging_ro\BCGW\physical_infrastructure\csv_file.csv   # *.csv Source Dataset CSV (comma separated) file
- DEST_SCHEMA = WHSE_IMAGERY_AND_BASE_MAPS   # Destination Schema (upper case please)
- FILE_CHANGE_DETECTION = TRUE   # Set to TRUE to enable (else disable) change detection
- DEST_DB_ENV_KEY = DLV   # Destination Database Keyword (DLV|TST|PRD)
- DEST_FEATURE_1 = GSR_zzz_SV   # Destination Feature 1
- DEST_FEATURE_2 = GSR_zzz_VW   # Destination Feature 2
- SUCCESS_EMAIL = mike.dunham-wilkie@gov.bc.ca   # Email address to send "Success" messages to
- FAILURE_EMAIL = dataetl@gov.bc.ca   # Email address to send "Failure" emails to
- FAILURE_MESSAGE = Load failed - please check FME logs   # Body of email message to send on failure
- DEST_FME_SERVER = http://ascella   # Dest FME server for Job Submitter
- LOGFILE:   # Python Script
      import DataBCFMWTemplate
      params = DataBCFMWTemplate.CalcParams(FME_MacroValues)
      return params.getFMWLogFileRelativePath()

Readers:
- CSV_1: CSV from $(SRC_DATASET_CSV_1)

Writers:
- NULL_1: NULL

CSV (reader CSV_1)
    attributes: col0 char(1)
    -> File_Change_Detector_v2 [FILE_SOURCE]
Note: Data Flow
File_Change_Detector_v2: File Change Detector v2
    CHANGES -> Sampler
Sampler
    RATE = 1
    SAMPLE_TYPE_LONG = First N Features
    SAMPLED -> FMEServerJobSubmitter
Note: Run Generic GSR File Loader
FMEServerJobSubmitter
    REPOSITORY = GSR_SUPPORT
    WORKSPACE_PARAMETERS = BUSINESS_ID string $(BUSINESS_ID) CUSTODIAN_ID string $(CUSTODIAN_ID) hasSourceDataID string $(hasSourceDataID) SOURCE_DATASET_CSV_1 string $(SRC_DATASET_CSV_1) DEST_DB_ENV_KEY string $(DEST_DB_ENV_KEY) SUCCESS_EMAIL string $(SUCCESS_EMAIL) FAILURE_EMAIL string $(FAILURE_EMAIL) FAILURE_MESSAGE string $(FAILURE_MESSAGE) DEST_FEATURE_2 string $(DEST_FEATURE_2) DEST_FEATURE_1 string $(DEST_FEATURE_1) DEST_FME_SERVER string $(DEST_FME_SERVER)
    WORKSPACE_NAME = gsr_occupants_sp_csv_staging_bcgw_driver.fmw
    PROCESSING_MODE = In Sequence
    USERNAME = dwrs
    PRIORITY = 100
    PASSWORD = dwrs_fme
    SERVER_NAME = $(DEST_FME_SERVER)
    BLOCKING = Yes
    JOB_SUCCEEDED -> Cloner
    JOB_FAILED -> FMEServerJobSubmitter_Failed
Note: create _numFeaturesOutput copies
Cloner
    COPYATT = _copynum
    COPIES = @Value(_numFeaturesOutput)
    COPY -> NULL (writer NULL_1)
Note: write them to the null device so they get counted
NULL (writer NULL_1)
FMEServerJobSubmitter_Failed: Logger
    MESSAGE = Feature is:
    MAXFEATS = 20
    MAXCOORDS = 20
    LOGGED -> Terminator
Terminator
    MESSAGE = Translation Terminated

Bookmark: Setup and Configuration
Note: WORKSPACE PROPERTIES / Complete workspace properties according to the instructions / provided as template values at the bottom of the Navigator widow
Note: DELIVERY PACKAGE / Container structure / <container> / this workbench.fmw / <bin> / DataBCWhse.py / <docs> / fme2012template.docx / <outputs> / <audt> / etlFileChangeLog.txt / etlPopulationLog.txt / <failed_features> / {tester outputs} / <log> / this workbench.log
Note: FILE NAMING CONVENTION / Components, separated by underscore characters ( _ ) / Components: / Destination layer name (warehouse name in full) / _Source location / _Source format / _Destination location / .fmw / Examples: / cbm_intgd_cadastral_fabric_sp_icfprd_sde_bcgw.fmw / raad_aoa_provincial_staging_shp_bcgw.fmw / spi_wildlife_nonsensitive_sp_idwprod1_svw_bcgw.fmw / site_env_remediation_sites_sp_idwprod1_odb_bcgw.fmw

Bookmark: Readers and Writers
Note: SOURCE DATA / - Specify full UNC path name for file sources (no mappings) / - Specify fully qualified names for all servers / - Delivery scripts should source delivery database instances / where they exist.
Note: DESTINATION DATA: DataBC Warehouse / Use one of the following writers for populating the warehouse: / - SDE30 (ESRI ArcSDE) / - ORACLE8I_DB (Oracle Non Spatial) / - ORACLE8I (Oracle Spatial Object) - by permission
Note: ORACLE NON SPATIAL AND SPATIAL OBJECT fast facts / - Destination Oracle Service: idwdlvr1.env.gov.bc.ca / - Username: <destination schema>
Note: ESRI ArcSDE (SDE30) WRITER fast facts / - Coordinate System: BCALB-83 / - ArcSDE Dataset: bcgwdlv.bcgov / - ArcSDE Server name: bcgwdlv.bcgov / - Instance: port:5156 / - User ID: <destination schema>

Bookmark: Parameters and Settings
Note: DESTINATION FEATURE PARAMETERS / Available on the properties pagefor each Destination Feature: / - Table Exists: Yes / - Drop Table First: N / - Truncate Table First: Y
Note: WORKSPACE PARAMETERS / - Workspace Title: name of script, less file extension / - Log File: .\outputs\log\<Workspace Title>.log / - Password: <no password> / - Startup Python Script: <provided> / - Shutdown Python Script: <provided>
Note: PRIVATE PARAMETERS / Publish the following parameters: / - Any data source name / - Any destination data service name / Add new published parameters for any / destination dataset being populated, with / the following characteristics: / - Type: text / - Name: DestFeature* / - Prompt: Destination Feature * / - Default Value: <name of destination feature> / * a number to distinguish between / multiple destination features. / Template includes private parameters: / - LogURL: URL to centralized logging service / - NotificationEmail: contact email

Bookmark: File-based change detection
Note: Attach a file-based dataset reader to the / FILE SOURCE input. File-based data / sources will be analyzed to determine if they / have changed since they were last replicated.
Note: The CHANGES output routes features from a / file-based source deemed to have changed / since its last replication. / The NO_CHANGES output routes features / from a file based source deemed to not have / changed since its last replication.
Note: If you have multiple data sources, / you may duplicate the FileChangeDetector / for each one, or fan them into a single / FileChangeDetector and then fan them / out again afterwards, based on an / identifying attribute.

FME custom transformer ArcSDELockRemover
Test description

Parameters:
- Data_Source = idwdlvr1.env.gov.bc.ca   # Destination Instance
- User_ID =   # User ID
- Password =
