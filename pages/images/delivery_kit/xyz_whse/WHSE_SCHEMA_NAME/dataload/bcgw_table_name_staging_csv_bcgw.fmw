FME workspace bcgw_table_name_staging_csv_bcgw.fmw
Title: bcgw_table_name_staging_csv_bcgw
Description: List Source and Destination datasets and describe any inline data manipulations
Usage: Describe processing summary 
    Counter Transformer: Provide a unique numeric value to primary key of the dataset.
History: June 26, 2013,G. Gale, DataBC,release 12.3 template for file sources,Sept 11, 2014,G. Gale, DataBC,release 13.1 template for file sources,Mar 24, 2015,Jxhong, Esri Canada,developed script for Ministry of International Trade, OneTool project team
Startup Python:
      import fme
      import DataBCFMWTemplate
      start = DataBCFMWTemplate.Start(fme)
      start.startup()
Shutdown Python:
      import fme
      import DataBCFMWTemplate
      shutIt = DataBCFMWTemplate.Shutdown(fme)
      shutIt.shutdown()

Parameters:
- DEST_FEATURE_1 = fill in the BCGW table name   # Destination Feature 1
- SRC_DATASET_CSV_1 =   # Source Comma Separated Value (CSV) File(s)
- FILE_CHANGE_DETECTION = TRUE   # Set to TRUE to enable (else disable) change detection
- DEST_DB_ENV_KEY = DLV   # Destination Database Keyword (DLV|TST|PRD)
- DEST_SCHEMA =   # Destination Schema
- LOGFILE:   # Python Script
      import DataBCFMWTemplate
      params = DataBCFMWTemplate.CalcParams(FME_MacroValues)
      return params.getFMWLogFileRelativePath()

Readers:
- CSV2_1: CSV2 from $(SRC_DATASET_CSV_1)

Writers:
- GEODATABASE_SDE_1: GEODATABASE_SDE

Note: CSV file in staging are
CSV (reader CSV2_1)
    attributes: col0 string
    -> File_Change_Detector_v2 [FILE_SOURCE]
File_Change_Detector_v2: File Change Detector v2
    CHANGES -> Counter
Note: Populate primary key values
Note: Import a BCGW feature type by selecting menu item Writers / Import Feature Types ... and then join it to the Counter.
Counter
    CNT_ATTR = shortname_SYSID
    DOMAIN = counter
    START = 1
    SCOPE = Global

FME custom transformer ArcSDELockRemover
Test description

Parameters:
- Data_Source = idwdlvr1.env.gov.bc.ca   # Destination Instance
- User_ID =   # User ID
- Password =

FME custom transformer File Change Detector
Provides routing for features from file-based data sources depending upon whether the source file has changed since the last time it was replicated.
Dependencies include:
 - python startup script to detect file change
 - etlAuditLog.txt file to record source file replications.  This file will be created if it does not exist.
 - python shutdown script to update the etlAuditLog file.

FILE_SOURCE (input)
    -> CD_1:_ExposeFMEDatasetName
Note: Step 1: Expose the 'fme_dataset' attribute. / For file-based data sources, this provides the full / path file name. This attribute provides a key to / retrieving the status indicator for file-based change / determined by the python startup script.
CD_1:_ExposeFMEDatasetName: AttributeExposer
    ATTR_LIST = fme_dataset
    -> CD_2:_RetrieveChangeStatus
Note: Step 2: Use the 'fme_dataset' value as a key / to retrieving a list of characteristics associated / with the file, as determined by the python startup / script. The following characteristics are provided / in a python list object: / [change detected: 'True' / 'False', file date] / index[0] index[1]
CD_2:_RetrieveChangeStatus: PythonCaller
    PYTHONSYMBOL = changeFlagFetcher
    PYTHONSOURCE:
      # class to retrieve a flag associated with the input feature's dataset
      # name that indicates whether or not the dataset has changed since the
      # last successful replication
      import pyfme
      import __main__ # FME_MacroValues are part of the __main__ namespace
      import string
      from string import upper

      global FME_MacroValues

      class changeFlagFetcher(object):
      	def __init__(self):
      		pass
      	def input(self, feature):

      		# dataset name is index to source file dictionary
      		fmeDataset = feature.getAttribute('fme_dataset')

      		# standardize use of \ in full path
      		dataset = fmeDataset.replace('/','\\')

      		# retrieve dictionary
      		sourceFileDictionary = __main__.changes

      		# dictionary is keyed on dataset name;
      		# corresponding value is python list ['True'|'False', File Date]
      		sourceList = sourceFileDictionary[dataset]

      		# first item in the list is 'True'|'False' indicator for change
      		changeIndicator = upper(str(sourceList[0]))

      		# create a new attribute with the true/false value
      		feature.setAttribute('CHANGE_DETECTED', changeIndicator)

      		self.pyoutput(feature)

      	def close(self):
      		pass
    -> CD_3:_ExposeChangeAttribute
Note: Step 3: A new CHANGE DETECTED / attribute is added to each feature, and / populated with the TRUE or FALSE / value determined in the python start / up script.
CD_3:_ExposeChangeAttribute: AttributeExposer
    ATTR_LIST = CHANGE_DETECTED
    -> CD_4:_FilterOnChangeDetected
Note: Step 4: Features are filtered according / to the CHANGE DETECTED boolean
CD_4:_FilterOnChangeDetected: AttributeFilter
    ATTR_NAME = CHANGE_DETECTED
    ATTR_VALUES = TRUE,FALSE
    TRUE -> CD_5:_CleanAttsFromChanged
    FALSE -> CD_6:_CleanAttsFromUnchanged
Note: Step 5: Features deemed to have been / sourced from a file dataset that has / changed are stripped of interim processing / attributes.
CD_5:_CleanAttsFromChanged: AttributeRemover
    REMOVE_ATTRS = CHANGE_DETECTED,fme_dataset
    -> CHANGES (output)
CHANGES (output)
Note: Step 6: Features deemed to have been / sourced from a file dataset that has not / changed are stripped of interim processing / attributes.
CD_6:_CleanAttsFromUnchanged: AttributeRemover
    REMOVE_ATTRS = CHANGE_DETECTED,fme_dataset
    -> NO_CHANGES (output)
NO_CHANGES (output)
